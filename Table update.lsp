(defun c:tableRegen()
	(setq ent (car (entsel "\nPick table for regeneration...")))
	(setq obj (vlax-ename->vla-object ent))
	(setq firstCellStyle (vlax-invoke-method obj 'GetCellStyle 0 0))
	(setq chars (strlen firstCellStyle))
	(if (> chars 13)
        (progn
			(setq titleStyle "TPA Title small")
			(setq dataStyle "TPA Data small")
		)
		(progn
			(setq titleStyle "TPA Title")
			(setq dataStyle "TPA Data")
		)
	)
	(setq rowCount (vlax-get-property obj 'Rows))
	(setq nn 0)
	;(command "DATALINKUPDATE" "U" ent "")
	;(command "DATALINKUPDATE" "U" ent "")
	(while (< nn rowCount)
		(if (= (vlax-invoke-method obj 'IsMergedCell nn 0 0 0 0 0) :vlax-true)
			(vlax-invoke-method obj 'SetCellStyle nn 0 titleStyle)
			(vlax-invoke-method obj 'SetCellStyle nn 0 dataStyle)	
		)
		(vlax-invoke-method obj 'SetRowHeight nn "0.1")
		(setq nn (1+ nn))
	)
)
	
	;(vlax-invoke-method obj 'SetCellStyle 0 0 "TPA Data")
	
	;(command "DATALINKUPDATE" "U" ent "")
	;(command "DATALINKUPDATE" "U" ent "")
	;(command "DATALINKUPDATE" "U" ent "")
