(defun c:tp()
  (getstring "\nPlease indicate orientation <Landscape Portrait>: ")
  (getstring "\nPlease indicate page size <A0 A1 A2 A3 A4>: ")
 ; (getstring "\nPlease indicate unit <Metric Imperial>")
 ; (setq orientation "landscape")
;  (setq size "A0")
  (setq acad (vlax-get-acad-object))
  (setq docs (vlax-get-property acad 'Documents))
  (setq doc (vlax-invoke-method docs 'Add "D:\\Work\\2061 Cad Standards Architect\\Received\\R1\\Interior Imperial.dwt"))
 ; (setq doc (vlax-get-property acad 'ActiveDocument))
  (setq layouts (vlax-get-property doc 'Layouts))
  (setq count (vlax-get-property layouts 'Count))
  (setq nn count)
  (while (> nn 0)
  	(setq nn (1- nn))
    (setq cur (vlax-invoke-method layouts 'Item nn))
    (setq name (vlax-get-property cur 'Name))
    (if (and (/= name "A0 Landscape") (/= name "Model"))
      (vlax-invoke-method cur 'Delete)
	)
  )
 
  (vlax-invoke-method doc 'Activate)
  (terpri)
  (terpri)
  
 )
 
 (defun c:av ()
   (getstring "\nPlease indicate orientation <Landscape Portrait>: ")
   (getstring "\nPlease indicate page size <A0 A1 A2 A3 A4>: ")
     (setq acad (vlax-get-acad-object))
  (setq docs (vlax-get-property acad 'Documents))
  (setq doc (vlax-get-property acad 'ActiveDocument))
  (setq layouts (vlax-get-property doc 'Layouts))
  (setq cur (vlax-invoke-method layouts 'Add "A2 Portrait"))
  (vlax-put-property doc 'ActiveLayout cur)
  (setq ps (vlax-get-property doc 'PaperSpace))
  (setq pt (list 0 0 0))
  (setq pts (vlax-3D-point pt))
  ;(vlax-invoke-method ps 'InsertBlock pts "D:\\Work\\2061 Cad Standards Architect\\Work\\A2 Portrait.dwg" 0 0 0 0)
  (command "insert" "D:\\Work\\2061 Cad Standards Architect\\Work\\A2 Portrait.dwg" "0,0,0" "" "" "")
  (command "._plot" "_n" "A2 Portrait" "A2 Portrait" "" "" "_y" "_n")
)
