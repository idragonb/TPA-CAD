(defun c:entsearch ()
	(setq test (getstring "\nEnter text style to find: "))
	(setq ent (entnext))
	(entsearch ent nil)
	(setq tbl (tblnext "BLOCK" T))
	(setq ent (cdr (assoc -2 tbl)))
	(entsearch ent tbl)
	(while (setq tbl (tblnext "BLOCK"))
		(setq ent (cdr (assoc -2 tbl)))
		(entsearch ent tbl)
	)
)
	
	
(defun entsearch (ent tbl)	
	(while (setq ent (entnext ent))
		(setq entlist (entget ent))
		(setq c8 (cdr (assoc 8 entlist)))
		(if (= c8 test)
			(progn
				(princ tbl)
				(princ entlist)
				(terpri)
			)

		)
		

	)
)

(defun c:scanblks ()
	(setq first T)
	(while (setq tbl (tblnext "BLOCK" first))
		(setq first nil)
		(setq c2 (cdr (assoc 2 tbl)))
		(princ c2)
		(terpri)
		(setq c-2 (cdr (assoc -2 tbl)))
		(textloc c-2)
	)
	(setq ent (entnext))
	(textloc ent)
)

(defun textloc(ent)
	(setq tstyle "_LLARGE");(getstring "\nEnter text style name: "))
	(setq newstyle "LLARGE");(getstring "\nEnter style name to change to: "))
	;(setq ent (entnext))
	(setq nn 0)
	(while (setq ent (entnext ent))
		(princ ".")
		(setq entlist (entget ent))
		(setq c0 (cdr (assoc 0 entlist)))
		(princ c0)
		(if (or (= c0 "TEXT") (= c0 "ATTRIB") (= "ATTDEF"))
			(setq c7 (cdr (assoc 7 entlist)))
		)
		(princ c7)
		(terpri)
		(if (= c7 tstyle)
			(progn
				(setq entlist (subst (cons 7 newstyle) (assoc 7 entlist) entlist))
				(entmod entlist)
				(entupd ent)
				(setq nn (1+ nn))
			)
		)
	)
	nn
)
